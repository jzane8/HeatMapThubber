string Names,result,external,position,areaVar;
numeric string HeatList,outputList;
int Number=0;
if (board){
  board(B) {
    sprintf(position,"Area: %f %f %f %f \n",
      u2mm(B.area.x1), u2mm(B.area.y1), u2mm(B.area.x2),
      u2mm(B.area.y2));
    outputList += position;
    B.elements(E) {
      E.attributes(A)
        {
          if(A.name == "MAXHEAT")
          {
            Number++;
            HeatList+=E.name;
            HeatList+= " ";
            sprintf(areaVar,"%f %f ",u2mm(E.x),u2mm(E.y));
            outputList += areaVar;
            if(E.footprint.area) {
              sprintf(areaVar,"%f ",(u2mm(E.footprint.area.x2)-u2mm(E.footprint.area.x1))*((u2mm(E.footprint.area.y2)-u2mm(E.footprint.area.y1))));
              outputList += areaVar;
            } else {
             sprintf(result,"no footprint");
             dlgMessageBox(result,"+OK");
            }
            outputList += A.value;
            outputList += "\n";
          }
        }
    }
    sprintf(result,"%d Parts, Max Heat Capacity:%s",Number,HeatList);
    dlgMessageBox(result,"+OK");
  }
  output("/Users/richardzane/Documents/EAGLE/ulps/HeatMapThubber/files/output.txt", "wt") {
    dlgMessageBox(outputList,"+OK");
    printf(outputList);
  }

  // system call to get values out of external python file. Right now the paths are hardcoded. The first is the location of my
  // Python executable, the second is the location of the python script that needs to be run.
  // The reason why they're global instead of relative to the local directory is because of a quirk in how EAGLE runs ULPs.

  int x = system("/usr/local/opt/python/bin/python3.7 /Users/richardzane/Documents/EAGLE/ulps/HeatMapThubber/drawHeat.py > /Users/richardzane/Documents/EAGLE/ulps/HeatMapThubber/o.txt 2> /Users/richardzane/Documents/EAGLE/ulps/HeatMapThubber/files/error.txt");
  if (x != 0){
    sprintf(external,"script exit code: %d",x);
    dlgMessageBox(external,"+OK");
  }
}





if (schematic)
  schematic(S)
          {
              S.parts(P)
              {
                 if (P.device.package)
                 {
                    P.attributes(A)
                    {
                      if(A.name)
                      {
                      Number++;
                      HeatList+=A.value;
                      HeatList+=", ";
                      }
                    }
                  }
              }
              sprintf(result,"%d Parts, Max Heat Capacity:%s",Number,HeatList);
              dlgMessageBox(result,"+OK");
            }
